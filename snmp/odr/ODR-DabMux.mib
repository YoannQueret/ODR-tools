-- OPENDIGITALRADIO SMIV2 SPECIFICATION MIB

OPENDIGITALRADIO-MIB DEFINITIONS ::= BEGIN

IMPORTS
    MODULE-IDENTITY,
    OBJECT-TYPE,
    enterprises,
    Integer32                     FROM SNMPv2-SMI;


dabmux MODULE-IDENTITY
     LAST-UPDATED "201802190000Z"
     ORGANIZATION "OpenDigitalRadio"
     CONTACT-INFO
        "OpenDigitalRadio
        opendigitalradio.org
 
        Postal: OpenDigitalRadio
        Rue de Lausanne 16
        1201 Geneve
        Switzerland
 
        EMail: info@opendigitalradio.org"
 
     DESCRIPTION
        "The MIB for ODR-DabMux"
 
     REVISION
        "201802190000Z"
 
     DESCRIPTION
        "First MIB version."
 
  ::= { opendigitalradio 1 }

opendigitalradio          OBJECT IDENTIFIER ::=  { enterprises 51436 }

mux1 OBJECT IDENTIFIER ::=  { dabmux 1 }

----------------------------------
-- General Info
----------------------------------
muxVersion OBJECT-TYPE
        SYNTAX  OCTET STRING
        MAX-ACCESS read-only
        STATUS  current
        DESCRIPTION
                "ODR-DabMux version"
        -- 1.3.6.1.4.1.51436.1.1
        ::= { mux1 1 }

muxInputCount OBJECT-TYPE
        SYNTAX  Integer32 (1..128)
        MAX-ACCESS read-only
        STATUS  current
        DESCRIPTION
                "Return : 0 Unknown, 1 NoData, 2 Unstable, 3 Silent, 4 Streaming"
        -- 1.3.6.1.4.1.51436.1.1
        ::= { mux1 2 }
        
muxInputState OBJECT-TYPE
        SYNTAX  Integer32 (0..4)
        MAX-ACCESS read-only
        STATUS  current
        DESCRIPTION
                "Return : 0 Unknown, 1 NoData, 2 Unstable, 3 Silent, 4 Streaming"
        -- 1.3.6.1.4.1.51436.1.1
        ::= { mux1 3 }

        
----------------------------------
-- inputTable 
----------------------------------
  
inputTable OBJECT-TYPE
        SYNTAX  SEQUENCE OF InputEntrySEQ
        MAX-ACCESS not-accessible
        STATUS  current
        DESCRIPTION
                ""
        -- 1.3.6.1.4.1.51436.1.10
        ::= { mux1 10 }

inputEntry OBJECT-TYPE
        SYNTAX  InputEntrySEQ
        MAX-ACCESS not-accessible
        STATUS  current
        DESCRIPTION
                ""
        INDEX {
                inputIndex }
        -- 1.3.6.1.4.1.51436.1.10.1
        ::= { inputTable 1 }


InputEntrySEQ ::= SEQUENCE {
        inputIndex              Integer32,
        inputName               OCTET STRING,
        inputUnderRun           Integer32,
        inputOverRun            Integer32,
        inputState              Integer32,
        inputLeftLevel          Integer32,
        inputRightLevel         Integer32,
        inputLeftLevelSlow      Integer32,
        inputRightLevelSlow     Integer32
        }
  
inputIndex OBJECT-TYPE
        SYNTAX  Integer32 (1..128)
        MAX-ACCESS read-only
        STATUS  current
        DESCRIPTION
                ""
        -- 1.3.6.1.4.1.51436.1.10.1.1
        ::= { inputEntry 1 }

inputName OBJECT-TYPE
        SYNTAX  OCTET STRING
        MAX-ACCESS read-only
        STATUS  current
        DESCRIPTION
                ""
        -- 1.3.6.1.4.1.51436.1.10.1.2
        ::= { inputEntry 2 }
        
inputUnderRun OBJECT-TYPE
        SYNTAX  Integer32
        MAX-ACCESS read-only
        STATUS  current
        DESCRIPTION
                ""
        -- 1.3.6.1.4.1.51436.1.10.1.3
        ::= { inputEntry 3 }
        
inputOverRun OBJECT-TYPE
        SYNTAX  Integer32
        MAX-ACCESS read-only
        STATUS  current
        DESCRIPTION
                ""
        -- 1.3.6.1.4.1.51436.1.10.1.4
        ::= { inputEntry 4 }

inputState OBJECT-TYPE
        SYNTAX  Integer32
        MAX-ACCESS read-only
        STATUS  current
        DESCRIPTION
                "Return : 0 Unknown, 1 NoData, 2 Unstable, 3 Silent, 4 Streaming"
        -- 1.3.6.1.4.1.51436.1.10.1.5
        ::= { inputEntry 5 }

inputLeftLevel OBJECT-TYPE
        SYNTAX  Integer32
        MAX-ACCESS read-only
        STATUS  current
        DESCRIPTION
                ""
        -- 1.3.6.1.4.1.51436.1.10.1.6
        ::= { inputEntry 6 }
        
inputRightLevel OBJECT-TYPE
        SYNTAX  Integer32
        MAX-ACCESS read-only
        STATUS  current
        DESCRIPTION
                ""
        -- 1.3.6.1.4.1.51436.1.10.1.7
        ::= { inputEntry 7 }
        
inputLeftLevelSlow OBJECT-TYPE
        SYNTAX  Integer32
        MAX-ACCESS read-only
        STATUS  current
        DESCRIPTION
                ""
        -- 1.3.6.1.4.1.51436.1.10.1.8
        ::= { inputEntry 8 }
        
inputRightLevelSlow OBJECT-TYPE
        SYNTAX  Integer32
        MAX-ACCESS read-only
        STATUS  current
        DESCRIPTION
                ""
        -- 1.3.6.1.4.1.51436.1.10.1.9
        ::= { inputEntry 9 }

END
