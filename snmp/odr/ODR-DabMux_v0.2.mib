-- OPENDIGITALRADIO SMIV2 SPECIFICATION MIB

OPENDIGITALRADIO-MIB DEFINITIONS ::= BEGIN

IMPORTS
    MODULE-IDENTITY,OBJECT-TYPE,
    NOTIFICATION-TYPE,enterprises,
    Integer32,IpAddress                     FROM SNMPv2-SMI
    TEXTUAL-CONVENTION,DisplayString        FROM SNMPv2-TC;


dabmux MODULE-IDENTITY
     LAST-UPDATED "201802190000Z"
     ORGANIZATION "OpenDigitalRadio"
     CONTACT-INFO
        "OpenDigitalRadio
        opendigitalradio.org
 
        Postal: OpenDigitalRadio
        Rue de Lausanne 16
        1201 Genève
        Switzerland
 
        EMail: info@opendigitalradio.org"
 
     DESCRIPTION
        "The MIB for ODR-DabMux"
 
     REVISION
        "201802190000Z"
 
     DESCRIPTION
        "First MIB version."
 
  ::= { opendigitalradio 1 }

opendigitalradio          OBJECT IDENTIFIER ::=  { enterprises 51436 }


----------------------------------
-- General Info
----------------------------------
time OBJECT-TYPE
        SYNTAX  DisplayString
        MAX-ACCESS read-only
        STATUS  current
        DESCRIPTION
                "ODR-DabMux version"
        -- 1.3.6.1.4.1.51436.1.1
        ::= { dabmux 1 }

----------------------------------
-- muxTable 
----------------------------------
  
muxTable OBJECT-TYPE
        SYNTAX  SEQUENCE OF inputEntrySEQ
        MAX-ACCESS not-accessible
        STATUS  current
        DESCRIPTION
                ""
        -- 1.3.6.1.4.1.51436.1.10
        ::= { dabmux 10 }
        
muxEntry OBJECT-TYPE
        SYNTAX  inputEntrySEQ
        MAX-ACCESS not-accessible
        STATUS  current
        DESCRIPTION
                ""
        INDEX {
                muxIndex }
        -- 1.3.6.1.4.1.51436.1.10.1
        ::= { muxTable 1 }

muxEntrySEQ ::= SEQUENCE {
        muxIndex            INTEGER32,
        muxName             DisplayString,
        muxStatsPort        INTEGER32,
        muxVersion          DisplayString,
        muxInputState       INTEGER32,
        muxInputDetails     SEQUENCE OF inputTable
        }
  
muxIndex OBJECT-TYPE
        SYNTAX  INTEGER32 (1..128)
        MAX-ACCESS read-only
        STATUS  current
        DESCRIPTION
                ""
        -- 1.3.6.1.4.1.51436.1.10.1.1
        ::= { muxEntry 1 }

muxName OBJECT-TYPE
        SYNTAX  DisplayString
        MAX-ACCESS read-only
        STATUS  current
        DESCRIPTION
                ""
        -- 1.3.6.1.4.1.51436.1.10.1.2
        ::= { muxEntry 2 }

muxStatsPort OBJECT-TYPE
        SYNTAX  INTEGER32
        MAX-ACCESS read-only
        STATUS  current
        DESCRIPTION
                ""
        -- 1.3.6.1.4.1.51436.1.10.1.3
        ::= { muxEntry 3 }

muxVersion OBJECT-TYPE
        SYNTAX  INTEGER32
        MAX-ACCESS read-only
        STATUS  current
        DESCRIPTION
                ""
        -- 1.3.6.1.4.1.51436.1.10.1.4
        ::= { muxEntry 4 }
        
muxInputState OBJECT-TYPE
        SYNTAX  INTEGER32
        MAX-ACCESS read-only
        STATUS  current
        DESCRIPTION
                ""
        -- 1.3.6.1.4.1.51436.1.10.1.5
        ::= { muxEntry 5 }
        
----------------------------------
-- inputTable 
----------------------------------
  
inputTable OBJECT-TYPE
        SYNTAX  SEQUENCE OF inputEntrySEQ
        MAX-ACCESS not-accessible
        STATUS  current
        DESCRIPTION
                ""
        -- 1.3.6.1.4.1.51436.1.10.1.20
        ::= { muxEntry 20 }

inputEntry OBJECT-TYPE
        SYNTAX  inputEntrySEQ
        MAX-ACCESS not-accessible
        STATUS  current
        DESCRIPTION
                ""
        INDEX {
                inputIndex }
        -- 1.3.6.1.4.1.51436.1.10.1.20.1
        ::= { inputTable 1 }


inputEntrySEQ ::= SEQUENCE {
        inputIndex            INTEGER32,
        inputName             DisplayString,
        inputUnderRun         INTEGER32,
        inputOversRun         INTEGER32,
        inputState            INTEGER32,
        inputLeftLevel        INTEGER32,
        inputRightLevel       INTEGER32,
        inputLeftLevelSlow    INTEGER32,
        inputRightLevelSlow   INTEGER32,
        }
  
inputIndex OBJECT-TYPE
        SYNTAX  INTEGER32 (1..128)
        MAX-ACCESS read-only
        STATUS  current
        DESCRIPTION
                ""
        -- 1.3.6.1.4.1.51436.1.10.1.20.1.1
        ::= { inputEntry 1 }

inputName OBJECT-TYPE
        SYNTAX  DisplayString
        MAX-ACCESS read-only
        STATUS  current
        DESCRIPTION
                ""
        -- 1.3.6.1.4.1.51436.1.10.1.20.1.2
        ::= { inputEntry 2 }
        
inputUnderRun OBJECT-TYPE
        SYNTAX  INTEGER32
        MAX-ACCESS read-only
        STATUS  current
        DESCRIPTION
                ""
        -- 1.3.6.1.4.1.51436.1.10.1.20.1.3
        ::= { inputEntry 3 }
        
inputOverRun OBJECT-TYPE
        SYNTAX  INTEGER32
        MAX-ACCESS read-only
        STATUS  current
        DESCRIPTION
                ""
        -- 1.3.6.1.4.1.51436.1.10.1.20.1.4
        ::= { inputEntry 4 }

inputState OBJECT-TYPE
        SYNTAX  INTEGER32
        MAX-ACCESS read-only
        STATUS  current
        DESCRIPTION
                "Return : 0 Unknown, 1 NoData, 2 Unstable, 3 Silent, 4 Streaming"
        -- 1.3.6.1.4.1.51436.1.10.1.20.1.5
        ::= { inputEntry 5 }

inputLeftLevel OBJECT-TYPE
        SYNTAX  INTEGER32
        MAX-ACCESS read-only
        STATUS  current
        DESCRIPTION
                ""
        -- 1.3.6.1.4.1.51436.1.10.1.20.1.6
        ::= { inputEntry 6 }
        
inputRightLevel OBJECT-TYPE
        SYNTAX  INTEGER32
        MAX-ACCESS read-only
        STATUS  current
        DESCRIPTION
                ""
        -- 1.3.6.1.4.1.51436.1.10.1.20.1.7
        ::= { inputEntry 7 }
        
inputLeftLevelSlow OBJECT-TYPE
        SYNTAX  INTEGER32
        MAX-ACCESS read-only
        STATUS  current
        DESCRIPTION
                ""
        -- 1.3.6.1.4.1.51436.1.10.1.20.1.8
        ::= { inputEntry 8 }
        
inputRightLevelSlow OBJECT-TYPE
        SYNTAX  INTEGER32
        MAX-ACCESS read-only
        STATUS  current
        DESCRIPTION
                ""
        -- 1.3.6.1.4.1.51436.1.10.1.20.1.9
        ::= { inputEntry 9 }

END
