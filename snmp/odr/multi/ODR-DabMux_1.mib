-- OPENDIGITALRADIO SMIV2 SPECIFICATION MIB

OPENDIGITALRADIO-MIB DEFINITIONS ::= BEGIN

IMPORTS
    MODULE-IDENTITY,
    OBJECT-TYPE,
    enterprises,
    Integer32                     FROM SNMPv2-SMI;

odrdabmux MODULE-IDENTITY
     LAST-UPDATED "201802190000Z"
     ORGANIZATION "OpenDigitalRadio"
     CONTACT-INFO
        "OpenDigitalRadio
        opendigitalradio.org
 
        Postal: OpenDigitalRadio
        Rue de Lausanne 16
        1201 Geneve
        Switzerland
 
        EMail: info@opendigitalradio.org"
     DESCRIPTION
        "The MIB for ODR-DabMux 1.3.6.1.4.1.51436.1.x
        51436.1    : OpenDigitalRadio ODR-DabMux
        51436.1.1  : OpenDigitalRadio ODR-DabMux multiplex 1 on the server
        51436.1.x  : OpenDigitalRadio ODR-DabMux multiplex x on the server
        "
     REVISION
        "201802190000Z"
     DESCRIPTION
        "First MIB version."
 
  ::= { opendigitalradio 1 }

opendigitalradio OBJECT IDENTIFIER ::=  { enterprises 51436 }

----------------------------------
-- mux identification
----------------------------------
mux1 OBJECT IDENTIFIER ::=  { odrdabmux 1 }


----------------------------------
-- mux Info
----------------------------------
muxStatPort OBJECT-TYPE
        SYNTAX  OCTET STRING
        MAX-ACCESS read-only
        STATUS  current
        DESCRIPTION
                "ODR-DabMux version"
        -- 1.3.6.1.4.1.51436.1.x.1
        ::= { mux1 1 }
        
muxVersion OBJECT-TYPE
        SYNTAX  OCTET STRING
        MAX-ACCESS read-only
        STATUS  current
        DESCRIPTION
                "ODR-DabMux version"
        -- 1.3.6.1.4.1.51436.1.x.2
        ::= { mux1 2 }

muxGlobalInputState OBJECT-TYPE
        SYNTAX  OCTET STRING
        MAX-ACCESS read-only
        STATUS  current
        DESCRIPTION
                "ODR-DabMux global input state
                Return : 0 Unknown, 1 NoData, 2 Unstable, 3 Silent, 4 Streaming"
        -- 1.3.6.1.4.1.51436.1.x.3
        ::= { mux1 3 }
        
----------------------------------
-- inputTable 
----------------------------------
  
muxInputTable OBJECT-TYPE
        SYNTAX SEQUENCE OF MuxInputEntrySEQ
        MAX-ACCESS not-accessible
        STATUS  current
        DESCRIPTION
                ""
        -- 1.3.6.1.4.1.51436.1.x.10
        ::= { mux1 10 }

muxInputEntry OBJECT-TYPE
        SYNTAX  MuxInputEntrySEQ
        MAX-ACCESS not-accessible
        STATUS  current
        DESCRIPTION
                ""
        INDEX {
                muxInputIndex }
        -- 1.3.6.1.4.1.51436.1.x.10.1
        ::= { muxInputTable 1 }


MuxInputEntrySEQ ::= SEQUENCE {
        muxInputIndex            Integer32,
        muxInputName             OCTET STRING,
        muxInputUnderRun         Integer32,
        muxInputOversRun         Integer32,
        muxInputState            Integer32,
        muxInputLeftLevel        Integer32,
        muxInputRightLevel       Integer32,
        muxInputLeftLevelSlow    Integer32,
        muxInputRightLevelSlow   Integer32
        }
  
muxInputIndex OBJECT-TYPE
        SYNTAX  Integer32 (1..128)
        MAX-ACCESS read-only
        STATUS  current
        DESCRIPTION
                ""
        -- 1.3.6.1.4.1.51436.1.x.10.1.1
        ::= { muxInputEntry 1 }

muxInputName OBJECT-TYPE
        SYNTAX  OCTET STRING
        MAX-ACCESS read-only
        STATUS  current
        DESCRIPTION
                ""
        -- 1.3.6.1.4.1.51436.1.x.10.1.2
        ::= { muxInputEntry 2 }
        
muxInputUnderRun OBJECT-TYPE
        SYNTAX  Integer32
        MAX-ACCESS read-only
        STATUS  current
        DESCRIPTION
                ""
        -- 1.3.6.1.4.1.51436.1.x.10.1.3
        ::= { muxInputEntry 3 }
        
muxInputOversRun OBJECT-TYPE
        SYNTAX  Integer32
        MAX-ACCESS read-only
        STATUS  current
        DESCRIPTION
                ""
        -- 1.3.6.1.4.1.51436.1.x.10.1.4
        ::= { muxInputEntry 4 }

muxInputState OBJECT-TYPE
        SYNTAX  Integer32
        MAX-ACCESS read-only
        STATUS  current
        DESCRIPTION
                "Return : 0 Unknown, 1 NoData, 2 Unstable, 3 Silent, 4 Streaming"
        -- 1.3.6.1.4.1.51436.1.x.10.1.5
        ::= { muxInputEntry 5 }

muxInputLeftLevel OBJECT-TYPE
        SYNTAX  Integer32
        MAX-ACCESS read-only
        STATUS  current
        DESCRIPTION
                ""
        -- 1.3.6.1.4.1.51436.1.x.10.1.6
        ::= { muxInputEntry 6 }
        
muxInputRightLevel OBJECT-TYPE
        SYNTAX  Integer32
        MAX-ACCESS read-only
        STATUS  current
        DESCRIPTION
                ""
        -- 1.3.6.1.4.1.51436.1.x.10.1.7
        ::= { muxInputEntry 7 }
        
muxInputLeftLevelSlow OBJECT-TYPE
        SYNTAX  Integer32
        MAX-ACCESS read-only
        STATUS  current
        DESCRIPTION
                ""
        -- 1.3.6.1.4.1.51436.1.x.10.1.8
        ::= { muxInputEntry 8 }
        
muxInputRightLevelSlow OBJECT-TYPE
        SYNTAX  Integer32
        MAX-ACCESS read-only
        STATUS  current
        DESCRIPTION
                ""
        -- 1.3.6.1.4.1.51436.1.x.10.1.9
        ::= { muxInputEntry 9 }

END
